module netapp {
    yang-version 1;
    namespace "urn:opendaylight:params:xml:ns:yang:netapp";
    prefix "netapp";

    revision "2015-01-05" {
        description "Initial revision of netapp model";
    }
}
